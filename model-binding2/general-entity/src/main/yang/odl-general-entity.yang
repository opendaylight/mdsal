module odl-general-entity {
    namespace "urn:opendaylight:params:xml:ns:yang:mdsal:core:general-entity";
    prefix "odl-general-entity";

    description "Defines a model to describe a general entity whose path can be used as an ID for an entity that isn't otherwise modelled";

    revision 2015-09-30 {
        description "Initial revision";
    }

    list entity {
        key name;
        leaf name {
            type string;
        }
    }
}
