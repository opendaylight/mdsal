module test {
    namespace "urn:test";
    prefix tst;

    revision 2017-06-27;

    typedef id {
        type uint16 {
          range "1..4094";
        }
    }

    container my-cont {
        leaf my-leaf {
            type string;
        }
    }
}
