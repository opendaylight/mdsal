module test-typedef {
    yang-version 1;
    namespace "urn:test:simple:test:typedef";
    prefix "typedef";

    revision "2017-08-29" {
    }

    typedef policy-logging-flag {
        description "false-disable,true-enable";
        type boolean;
    }

    typedef typedef-empty {
        type empty;
    }

    container default-policy{
      leaf action {
        type boolean;
      }

      leaf action2 {
        type policy-logging-flag;
      }

      leaf action3 {
        type boolean;
        default "true";
      }
    }

    container test-cont{
      leaf empty-leaf {
        type empty;
      }

      leaf empty-leaf2 {
        type typedef-empty;
      }

      leaf empty-leaf3{
         type empty;
         default "";
      }
    }
}
