module test {
    yang-version 1;
    namespace "urn:test:simple:test";
    prefix test;

    organization "test.org";

    revision "2017-03-10";

    container my-cont {
    }

    container my-cont2 {
        leaf my-leaf {
            type string;
        }
        leaf my-leaf2 {
            type string;
        }
    }
}
