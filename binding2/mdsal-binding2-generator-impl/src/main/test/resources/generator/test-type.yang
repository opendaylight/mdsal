module test-type {
    yang-version 1;

    namespace "urn:test:simple:test:type";
    prefix test-type;
    organization "test.type.org";
    revision "2017-02-09";

    typedef my-type {
        type string;
    }

}
