module test-anyxml {
    yang-version 1;

    namespace "urn:test:simple:test:anyxml";
    prefix test;
    organization "test.org";
    revision "2017-06-07";

    container .my-cont {
      container my-inner-cont {
        leaf my-leaf {
          type string;
        }

        anyxml inner-anyxml {
          description "I am data schema node anyxml";
        }
      }
    }

    anyxml root-anyxml {
       description "I am root anyxml";
    }
}
