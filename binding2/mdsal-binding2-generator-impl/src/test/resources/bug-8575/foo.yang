module foo {

    namespace "foo";
    prefix foo;

    revision 2017-05-15;

    grouping A{
      container A1 {
        leaf leaf-A-A1 {
            type string;
        }
      }
    }

    container A{
        leaf leaf-A {
            type string;
        }
    }
}
