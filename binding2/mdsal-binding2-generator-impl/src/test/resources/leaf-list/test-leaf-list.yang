module test-leaf-list {
    yang-version 1;
    namespace "org.test.leaf-list";
    prefix "ll";

    container *1my-cont {
        leaf-list min-max-leaf-list {
            min-elements 1;
            max-elements 3;
            type string;
        }

        leaf-list unbounded-leaf-list {
            type string;
        }

        list unkeyed-list {
            max-elements 1;
            leaf unkeyed-leaf {
                type string;
            }
        }
    }
}
