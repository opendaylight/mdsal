module test-action {
    yang-version 1.1;
    namespace "urn:test:action";
    prefix "routed";

    revision "2017-06-21" {
        description
            "Initial revision";
    }

    container my-cont {
        action in-cont {
            input {
                leaf input-leaf {
                    type string;
                }
            }

            output {
                leaf output-leaf {
                    type string;
                }
            }
        }
    }

    list my-list {
        key "name";

        leaf name {
            type string;
        }

        action in-list {
            input {
                leaf input-list-leaf {
                    type string;
                }
            }

            output {
                leaf output-list-leaf {
                    type string;
                }
            }
        }
    }
}
