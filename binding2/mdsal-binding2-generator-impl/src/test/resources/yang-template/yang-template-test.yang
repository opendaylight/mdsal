module yang-template-test {
    yang-version 1.1;
    namespace "org.opendaylight.yang.template";
    prefix "ytemp";

    import yang-template-import { prefix "yti"; revision-date 2016-06-23; }

    revision 2016-01-01 {
        description "Simple yang missing deviation statement";
    }

    typedef simple-typedef {
        type string;
        default "simple-typedef";
    }

    container simple-container {
    }

    anyxml simple-anyxml-mandatory {
        mandatory true;
    }

    anydata simple-anydata;

    anydata simple-anydata-mandatory {
        mandatory true;
    }

    container simple-container-with-action {
        action act {
            input {
                leaf reset-at {
                    type string;
                    mandatory true;
                }
            }
            output {
                leaf reset-finished-at {
                    type string;
                    mandatory true;
                }
            }
        }
    }

    leaf simple-leaf {
        type string;
    }

    leaf-list simple-leaf-list {
        type string;
    }

    leaf-list simple-leaf-list-userordered {
        ordered-by user;
        type string;
    }

    list simple-list {
        key "simple-list-leaf-1";
        unique "simple-list-leaf-2";
        leaf simple-list-leaf-1 {
            type string;
        }
        leaf simple-list-leaf-2 {
            type string;
        }
    }

    list simple-list-more-arg-in-unique {
        key "simple-list-leaf-1";
        unique "simple-list-leaf-1 simple-list-leaf-2";
        leaf simple-list-leaf-1 {
            type string;
        }
        leaf simple-list-leaf-2 {
            type string;
        }
    }

    list simple-list-userordered {
        ordered-by user;
        key "simple-list-userordered-leaf-1";
        unique "simple-list-userordered-leaf-2";
        leaf simple-list-userordered-leaf-1 {
            type string;
        }
        leaf simple-list-userordered-leaf-2 {
            type string;
        }
    }

    choice simple-choice {
        case simple-case-1 {
            leaf simple-case-1-leaf {
                type string;
            }
        }
        case simple-case-2 {
            leaf simple-case-2-leaf {
                type string;
            }
        }
    }

    anyxml simple-anyxml;

    container simple-container-uses {
        uses simple-grouping {
            refine simple-grouping-leaf {
                description "refined simple-grouping-leaf description";
            }
        }
    }

    grouping simple-grouping {
        leaf simple-grouping-leaf {
            description "simple-grouping-leaf description";
            type string;
        }
    }

    augment "/simple-container-uses" {
        leaf augment-leaf {
            type string;
        }
    }

    extension simple-extension {
        description "simple-extension";
        argument simple-extension-argument;
    }

    feature simple-feature {
        description "simple-feature definex if device has some feature... hdd";
    }

    identity simple-identity {
        description "simple-identity";
    }

    notification simple-notification {
        leaf notification-leaf {
            type string;
        }
    }

    rpc simple-rpc {
        input {
            leaf rpc-input-leaf {
                type string;
            }
        }
    }
}
