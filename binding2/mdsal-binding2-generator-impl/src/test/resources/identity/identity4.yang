module identity4-module {
  yang-version 1.1;
  namespace "identity4:module";

  prefix "ide4mod";

  revision 2018-02-27;

  identity iden1 {
  }

  identity iden2 {

  }

  identity iden3 {
    base iden1;
    base iden2;
  }

  identity iden4 {
    base iden3;
  }
}
