module identity-module {
  yang-version 1.1;
  namespace "identity:module";

  prefix "idemod";

  revision 2017-06-01;

  import identity-import {
    prefix "ideimp";
  }

  identity iden1 {
  }

  identity iden2 {
    base "idemod:iden1";
  }

  identity iden3 {
    base "ideimp:iden1";
  }

  identity iden4 {
    base "idemod:iden2";
  }
}
