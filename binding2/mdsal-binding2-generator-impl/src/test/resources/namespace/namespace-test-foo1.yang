module namespace-test-foo1   {
    namespace "org.test.namespace.foo1";
    prefix "foo1";
    revision 2017-05-19;

    container a {
        container b {
            leaf c {
                type string;
            }
        }
    }

    grouping a {
         container b {
            leaf c {
                type string;
            }
        }
    }
}
