module namespace-test-dto {
    namespace "org.test.namespace.dto";
    prefix "dto";
    revision 2017-05-19;

    container a {
        container b {
            leaf leaf-b {
                type string;
            }
        }
    }

    grouping c {
        container d {
            leaf leaf-d {
                type string;
            }
        }
    }
}
