module class-type-test {

    description "ODL BGPCEP snippet challenge";

    prefix "class";
    namespace "org.class.type.test";

    container my-cont {         //data.myCont, dto.myContBuilder
        uses classtype-object;   //data.my_cont.ClassType, dto.my_cont.ClassTypeBuilder
    }

    typedef class-type {        //type.classType
        type uint8 {
            range 1..7;
        }
    }

    grouping classtype-object { //grp.ClassTypeObjectGrouping
        container class-type {   //grp.classtype_object.ClassTypeData
        leaf class-type {     //public type.ClassType getClassType()
                type class-type;
            }
        }
    }
}
