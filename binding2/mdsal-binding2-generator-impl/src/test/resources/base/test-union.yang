module test-union-module {
    yang-version 1.1;

    namespace "urn:test:simple:union";
    prefix tlfb;
    organization "leaf.union.org";
    revision "2017-03-14";

    leaf foo {
        type union {
            type int32;
            type enumeration {
              enum "en";
            }
        }
        description "I am leaf.";
    }
}
