module test-module {
    yang-version 1.1;

    namespace "urn:test:base:module";
    prefix test-base-module;
    organization "test.org.base.module";
    revision "2017-04-06";

    description "Base test module description";
}
