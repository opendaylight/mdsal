module test {

    yang-version 1;
    namespace "urn:test:simple:test";
    prefix "test";

    import test-import { prefix "imported-test"; revision-date 2017-04-21; }

    revision 2017-02-06;

    typedef my-type {
        type int8;
    }

    container .my-cont {
    }
}
