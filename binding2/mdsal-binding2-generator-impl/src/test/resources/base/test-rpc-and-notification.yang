module test-rpc-and-notification-module {
  yang-version 1;
  namespace "urn:base:test-rpc-and-notification";
  prefix base-test-rpc-and-notification;
  organization "yang-test-rpc-and-notification";
  revision "2017-04-06";

  rpc my-rpc {
    input {
      leaf in {
        type string;
      }
    }

    output {
      leaf out {
        type string;
      }
    }
  }

  notification my-notification {
  }

}
