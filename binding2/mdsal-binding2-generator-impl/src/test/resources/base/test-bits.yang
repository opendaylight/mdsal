module test-bits-module {
    yang-version 1.1;

    namespace "urn:test:simple:bits";
    prefix tlfb;
    revision "2017-03-14";

    typedef mybits-type {
        type bits {
          bit disable-nagle {
            position 0;
          }
          bit auto-sense-speed {
            position 1;
          }
          bit ten-mb-only {
            position 2;
          }
        }
      }

      leaf mybits {
        type mybits-type;
        default "auto-sense-speed";
      }
}
