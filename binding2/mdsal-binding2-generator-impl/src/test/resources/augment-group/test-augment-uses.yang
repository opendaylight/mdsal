module augment-test-uses {
    prefix "foo";
    namespace "org.test.augment.uses";

    container foo1 {
        leaf my-leaf {
            type string;
        }
    }

    augment /foo:foo1 {
        uses grp;
        leaf bar {
            type string;
        }
    }

    augment /foo:foo1 {
        leaf baz {
            type string;
        }
    }

    grouping grp {
        leaf my-grp-leaf {
            type string;
        }
    }
}
