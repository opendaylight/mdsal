module augment-identifier-test {
    prefix "foo";
    namespace "org.test.augment.identifier";

    import yang-ext {
      prefix ext;
    }

    container foo1 {
        leaf my-leaf {
            type string;
        }
    }

    augment /foo:foo1 {
        leaf bar {
            type string;
        }
    }

    augment /foo:foo1 {
        leaf baz {
            type string;
        }
    }
    container foo2 {
      leaf foo2-leaf {
          type string;
      }
    }

    augment /foo:foo2 {
      ext:augment-identifier i-am-new-identifier;

      leaf aug-foo2-leaf {
          type string;
      }
    }
}
