module augment-test-uses-grouping {
    prefix "foo";
    namespace "org.test.augment.uses.grouping";

    container foo1 {
        leaf my-leaf {
            type string;
        }
    }

    augment /foo:foo1 {
        uses grp {
           augment my-cont {
              leaf my-uses-grp-leaf {
                  type string;
              }
           }
        }

        leaf bar {
            type string;
        }
    }

    augment /foo:foo1 {
        leaf baz {
            type string;
        }
    }

    grouping grp {
        container my-cont {
            leaf my-grp-leaf {
              type string;
            }
        }
    }
}
