module test-union {
    yang-version 1;

    namespace "urn:test:simple:test:union";
    prefix test-union;
    organization "test.union.org";
    revision "2017-03-08";

    typedef my-union {
        type union {
	       type int32;
	       type string;
        }
    }

}
