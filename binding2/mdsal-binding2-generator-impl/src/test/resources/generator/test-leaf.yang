module test-lesf-module {
    yang-version 1.1;

    namespace "urn:test:simple:test:leaf";
    prefix tlf;
    organization "leaf.list.org";
    revision "2017-03-14";

    leaf foo {
        type string;
    }
}
