module test {
    yang-version 1;

    namespace "urn:test:simple:test";
    prefix test;
    organization "test.org";
    revision "2017-02-06";

    typedef my-type {
      type int8;
    }

    container _.my-cont {
      container my-inner-cont {
        leaf my-leaf {
          type string;
        }

        leaf my-leaf2 {
          type my-type;
        }
      }
    }

    container my-union-cont {
      leaf my-union-leaf {
        type union {
          type int8;
          type int16;
        }
      }
    }

    grouping my-grouping {
      container _.my-cont {
      }
    }
}
