module test {
    yang-version 1;

    namespace "urn:test:simple:test";
    prefix test;
    organization "test.org";
    revision "2017-02-06";

    container my-cont {
    }
    
    augment "/my-cont" {
        leaf augment-leaf {
            type string;
        }
    }
}
