module test-apple {

    yang-version 1;
    namespace "urn:test:simple:apple";
    prefix "test-apple";

    revision 2017-05-03;

    container apple {
        leaf apple {
            type enumeration {
                enum apple {
                    value 0 ;
                }
                enum apple1 {
                    value 1 ;
                }
            }
        }
    }
}
