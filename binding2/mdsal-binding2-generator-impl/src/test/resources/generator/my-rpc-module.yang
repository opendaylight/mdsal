module my-rpc-module {
  yang-version 1;
  namespace "urn:my-rpc-module:simple:test";
  prefix my-rpc-module;
  organization "yang-positive-smurfs";
  revision "2017-03-24";

  rpc my-call {
    input {
      leaf v1 {
        type string;
      }
    }

    output {
      leaf v2 {
        type string;
      }
    }
  }
}
