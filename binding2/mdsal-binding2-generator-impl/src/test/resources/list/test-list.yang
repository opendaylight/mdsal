module test-list {
    yang-version 1.1;

    namespace "urn:test:simple:test:list";
    prefix test-list;
    organization "test.list.org";
    revision "2017-03-14";

    list my-list {
        key "name";
        leaf name {
            type string;
        }

        leaf surname {
            type string;
        }
    }

}
