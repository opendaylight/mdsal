module test-list2 {
    yang-version 1.1;

    namespace "urn:test:simple:test:list2";
    prefix test-list2;
    organization "test.list2.org";
    revision "2017-03-14";

    list my-list {
        key "key key1 key2";
        leaf key{
            type string;
        }
        leaf key1 {
            type string;
        }
        leaf key2 {
            type string;
        }
        leaf foo{
            type string;
        }
    }

}
