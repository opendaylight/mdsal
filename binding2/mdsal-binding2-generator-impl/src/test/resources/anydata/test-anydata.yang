module test-anydata {
    yang-version 1.1;

    namespace "urn:test:simple:test:anydata";
    prefix test;
    organization "test.org";
    revision "2017-06-08";

    container .my-cont {
      container my-inner-cont {
        leaf my-leaf {
          type string;
        }

        anydata inner-anydata {
          description "I am data schema node anydata";
        }
      }
    }

    anydata root-anydata {
       description "I am root anydata";
    }
}
