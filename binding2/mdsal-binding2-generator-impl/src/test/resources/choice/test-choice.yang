module test-choice {
    yang-version 1;
    namespace "org.test.choice";
    prefix "tstch";

    container food {
        choice snack {
            case sports-arena {
                leaf pretzel {
                    type empty;
                }

                leaf beer {
                    type empty;
                }
            }

            case late-night {
                leaf chocolate {
                    type enumeration {
                        enum dark;
                        enum milk;
                        enum first-available;
                    }
                }
            }
        }
    }
}
