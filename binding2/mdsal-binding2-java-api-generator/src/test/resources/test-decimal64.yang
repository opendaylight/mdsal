module test-decimal64{
    namespace "urn:test:decimal64";
    prefix decimal64;
    revision 2017-01-01;

    typedef my-decimal64 {
        type decimal64 {
            fraction-digits 4;
        }
    }

    leaf ext-decimal64 {
        type my-decimal64;
        default "3.14";
    }

    leaf leaf-decimal64 {
        type decimal64 {
            fraction-digits 4;
        }
        default "3.14";
    }
}
