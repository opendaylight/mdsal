module test-restriction{
    namespace "urn:test:restriction";
    prefix restriction;
    revision 2017-01-01;

    typedef res {
      type string {
        pattern "[a-z]*";
      }
    }

    container cont {
        leaf test {
            type string {
              pattern [a-zA-Z_][a-zA-Z0-9\-_.]*;
              pattern [xX][mM][lL].*;
            }
        }

        leaf test2 {
              type string {
                pattern "[0-9]*";
              }
          }
        }
}
