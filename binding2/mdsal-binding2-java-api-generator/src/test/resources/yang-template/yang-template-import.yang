module yang-template-import {
    yang-version 1;
    namespace "org.opendaylight.yang.template.import";
    prefix "yti";

    revision 2016-06-23 {
        description "Simple yang for import";
    }

    leaf yti-leaf {
        type string;
    }

    extension ext;

    extension ext-arg {
        argument arg;
    }

    yti:ext;

    yti:ext-arg "arg";
}
