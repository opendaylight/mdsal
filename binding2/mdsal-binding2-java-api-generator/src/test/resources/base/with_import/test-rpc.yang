module test-rpc {

    yang-version 1;
    namespace "urn:test:simple:test:rpc";
    prefix "test-rpc";

    revision 2017-05-05;

    rpc hello-world {
        input {
            leaf name {
                type string;
            }
        }
        output {
            leaf greeting {
                type string;
            }
        }
    }
}
