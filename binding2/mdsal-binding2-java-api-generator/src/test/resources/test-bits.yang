module test-bits{
    namespace "urn:test:bits";
    prefix bits;
    revision 2017-01-01;

    typedef my-bits {
        type bits {
            bit ctrl;
            bit alt {
                position 5;
            }
            bit delete;
        }
    }
}
