module test-recursive-unions{
    namespace "urn:test:unions";
    prefix unions;
    revision 2017-01-01;

    typedef my-binary {
        type binary;
    }

    typedef ext-binary {
        type my-binary;
    }

    typedef my-bits {
        type bits {
            bit ctrl;
            bit alt {
                position 5;
            }
            bit delete;
        }
    }

    grouping apple {
        container apple {
            leaf apple {
                type union {
                    type my-bits;
                    type ext-binary;
                    type instance-identifier;
                    type int32;
                    type string;
                    type boolean;
                    type union {
                        type int64;
                        type union {
                           type int64;
                           type int32;
                        }
                    }
                }
            }
        }
    }
}
