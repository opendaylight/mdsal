module odl-test-foo-Bar {
    yang-version 1;
    namespace "urn:opendaylight:params:xml:ns:yang:mdsal:binding2:test:foo-Bar";
    prefix "fmB";

    description
        "One of several modules for testing collisions due to too similar namespaces.";

    revision "2016-04-20" {
        description
            "Initial revision, for ODL Boron.";
    }

}
