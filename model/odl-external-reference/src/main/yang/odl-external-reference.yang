module odl-external-reference {
    // vi: set et smarttab sw=4 tabstop=4:

    yang-version 1;
    namespace "urn:opendaylight:params:xml:ns:yang:external:reference";
    prefix "extref";

    organization "Cisco Systems, Inc.";

    contact "Robert Varga <rovarga@cisco.com>";

    description
        "Model defining the base type for external references for use instead
        of an instance-identifier, which does not allow referencing entities
        unknown in the model (due to imports, etc.).

        Copyright (c) 2016 Cisco Systems, Inc. and others.  All rights reserved.

        This program and the accompanying materials are made available under the
        terms of the Eclipse Public License v1.0 which accompanies this distribution,
        and is available at http://www.eclipse.org/legal/epl-v10.html";

    revision "2016-01-29" {
        description "Initial model";
    }

    typedef external-reference {
        description "Reference to a YANG-modeled node which resides outside
            of this system. The format must use module names as namespace
            prefixes -- in a similar fashion RESTCONF does. The reference
            is evaluated from the root of the external system.

            This data type does not hold the coordinates of the external
            system, nor does it specify which data store on the external
            system should be used to satisfy the reference. This information
            should be described in the model which instantiates a leaf of
            this type.";
        type string;
    }
}
