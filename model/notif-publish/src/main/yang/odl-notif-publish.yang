module odl-notif-publish {
    yang-version 1;
    namespace "urn:org:opendaylight:mdsal:notif-publish";
    prefix "np";

    contact "Robert Varga <rovarga@cisco.com>";

    description 
            "Copyright (c) 2015 Cisco Systems, Inc. and others.  All rights reserved.

            This program and the accompanying materials are made available under the
            terms of the Eclipse Public License v1.0 which accompanies this distribution,
            and is available at http://www.eclipse.org/legal/epl-v10.html";

    revision "2015-11-05" {
        description "Initial revision";
    }

    // FIXME: this should be a separate model
    typedef schema-node-identifier {
        description
           "";
        type string {
            pattern "/.*";
        }
    }

    // FIXME: this should be a separate model
    grouping embedded-data {
        leaf identifier {
            type schema-node-identifier;
            mandatory true;
        }
        anyxml value {
            mandatory true;
        }
    }

    rpc publish-notification {
        description
           "";

        list input {
            uses embedded-data;
        }
    }
}
