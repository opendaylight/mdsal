module ietf-restconf {
     namespace "urn:ietf:params:xml:ns:yang:ietf-restconf";
     prefix "rc";

     organization
       "IETF NETCONF (Network Configuration) Working Group";

     contact
       "WG Web:   <http://tools.ietf.org/wg/netconf/>
        WG List:  <mailto:netconf@ietf.org>

        WG Chair: Mehmet Ersue
                  <mailto:mehmet.ersue@nsn.com>

        WG Chair: Mahesh Jethanandani
                  <mailto:mjethanandani@gmail.com>

        Editor:   Andy Bierman
                  <mailto:andy@yumaworks.com>

        Editor:   Martin Bjorklund
                  <mailto:mbj@tail-f.com>

        Editor:   Kent Watsen
                  <mailto:kwatsen@juniper.net>";

     description
       "This module contains conceptual YANG specifications
        for basic RESTCONF media type definitions used in
        RESTCONF protocol messages.

        Note that the YANG definitions within this module do not
        represent configuration data of any kind.
        The 'restconf-media-type' YANG extension statement
        provides a normative syntax for XML and JSON message
        encoding purposes.

        Copyright (c) 2015 IETF Trust and the persons identified as
        authors of the code.  All rights reserved.

        Redistribution and use in source and binary forms, with or
        without modification, is permitted pursuant to, and subject
        to the license terms contained in, the Simplified BSD License
        set forth in Section 4.c of the IETF Trust's Legal Provisions
        Relating to IETF Documents
        (http://trustee.ietf.org/license-info).

        This version of this YANG module is part of RFC XXXX; see
		the RFC itself for full legal notices.";

     // RFC Ed.: replace XXXX with actual RFC number and remove this
     // note.

     // RFC Ed.: remove this note
     // Note: extracted from draft-ietf-netconf-restconf-08.txt

     // RFC Ed.: update the date below with the date of RFC publication
     // and remove this note.
     revision 2015-10-18 {
       description
         "Initial revision.";
       reference
         "RFC XXXX: RESTCONF Protocol.";
     }

     extension restconf-media-type {
      argument media-type-id {
        yin-element true;
      }
      // RFC Ed.: replace draft-ietf-netmod-yang-json with RFC number
      // in the description below, and remove this note.
      description
        "This extension is used to specify a YANG data structure which
         represents a conceptual RESTCONF media type.
         Data definition statements within this extension specify
         the generic syntax for the specific media type.

         YANG is mapped to specific encoding formats outside the
         scope of this extension statement. RFC 6020 defines XML
         encoding rules for all RESTCONF media types that use
         the '+xml' suffix. draft-ietf-netmod-yang-json defines
         JSON encoding rules for all RESTCONF media types that
         use the '+json' suffix.

         The 'media-type-id' parameter value identifies the media type
         that is being defined. It contains the string associated
         with the generic media type, i.e., no suffix is specified.

         This extension is ignored unless it appears as a top-level
         statement. It SHOULD contain data definition statements
         that result in exactly one container data node definition.
         This allows compliant translation to an XML instance
         document for each media type.

         The module name and namespace value for the YANG module using
         the extension statement is assigned to instance document data
		 conforming to the data definition statements within
         this extension.

         The sub-statements of this extension MUST follow the
         'data-def-stmt' rule in the YANG ABNF.

         The XPath document root is the extension statement itself,
         such that the child nodes of the document root are
         represented by the data-def-stmt sub-statements within
         this extension. This conceptual document is the context
         for the following YANG statements:

            - must-stmt
            - when-stmt
            - path-stmt
            - min-elements-stmt
            - max-elements-stmt
            - mandatory-stmt
            - unique-stmt
            - ordered-by
            - instance-identifier data type

         The following data-def-stmt sub-statements have special
         meaning when used within a restconf-resource extension
         statement.

         - The list-stmt is not required to have a key-stmt defined.
         - The if-feature-stmt is ignored if present.
         - The config-stmt is ignored if present.
         - The available identity values for any 'identityref'
           leaf or leaf-list nodes is limited to the module
           containing this extension statement, and the modules
           imported into that module.
         ";
     }

     rc:restconf-media-type "application/yang.errors" {
       uses errors;
     }

     rc:restconf-media-type "application/yang.api" {
       uses restconf;
     }

     grouping errors {
       description
         "A grouping that contains a YANG container
          representing the syntax and semantics of a
          YANG Patch errors report within a response message.";

       container errors {
         description
           "Represents an error report returned by the server if
            a request results in an error.";

         list error {
           description
             "An entry containing information about one
              specific error that occurred while processing
              a RESTCONF request.";
           reference "RFC 6241, Section 4.3";

           leaf error-type {
             type enumeration {
               enum transport {
                 description "The transport layer";
               }
               enum rpc {
                 description "The rpc or notification layer";
               }
               enum protocol {
                 description "The protocol operation layer";
               }
               enum application {
                 description "The server application layer";
               }
             }
             mandatory true;
             description
               "The protocol layer where the error occurred.";
           }

           leaf error-tag {
             type string;
             mandatory true;
             description
               "The enumerated error tag.";
           }

           leaf error-app-tag {
             type string;
             description
               "The application-specific error tag.";
           }

           leaf error-path {
             type instance-identifier;
             description
               "The YANG instance identifier associated
                with the error node.";
           }

           leaf error-message {
             type string;
             description
               "A message describing the error.";
           }

           anyxml error-info {
              description
                "This anyxml value MUST represent a container with
                zero or more data nodes representing additional
                error information.";
           }
         }
       }
     }

     grouping restconf {
       description
         "Conceptual container representing the
          application/yang.api resource type.";

       container restconf {
         description
           "Conceptual container representing the
            application/yang.api resource type.";

         container data {
           description
             "Container representing the application/yang.datastore
              resource type. Represents the conceptual root of all
              operational data and configuration data supported by
              the server.  The child nodes of this container can be
              any data resource (application/yang.data), which are
              defined as top-level data nodes from the YANG modules
              advertised by the server in the ietf-restconf-monitoring
              module.";
         }

         container operations {
           description
             "Container for all operation resources
              (application/yang.operation),
              Each resource is represented as an empty leaf with the
              name of the RPC operation from the YANG rpc statement.

              E.g.;

                 POST /restconf/operations/show-log-errors

                 leaf show-log-errors {
                   type empty;
                 }
             ";
         }
       }
     }

   }
