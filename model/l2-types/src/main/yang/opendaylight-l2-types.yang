module opendaylight-l2-types {
    namespace "urn:opendaylight:l2:types";
    prefix "ethertype";

    description
        "Copyright (c) 2013 Cisco Systems, Inc. and others.  All rights reserved.

         This program and the accompanying materials are made available under the
         terms of the Eclipse Public License v1.0 which accompanies this distribution,
         and is available at http://www.eclipse.org/legal/epl-v10.html";

    revision "2013-08-27" {
        description "Initial revision";
    }

    typedef vlan-pcp {
        description
            "IEEE 802.1p priority. It indicates the frame priority level.
             Values are from 0 (best effort) to 7 (highest);
             1 represents the lowest priority.";
        type uint8 {
            range "0..7";
        }
    }

    typedef vlan-dei {
        description
            "Drop Eligible Indicator (DEI): a 1-bit field. (formerly CFI).
             May be used separately or in conjunction with PCP to indicate frames
             eligible to be dropped in the presence of congestion.";
        type boolean;
    }

    typedef vlan-id {
        type uint16 {
            range "0..4095";
        }
    }

    typedef ether-type {
        type uint32;
    }
}
