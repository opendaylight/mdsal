module bug6183 {

    namespace "odl:test:bug6183";
    prefix "b";
    revision 2016-07-11;

    choice my-choice {
        container implicit-case-container {
        }
    }

    augment "/my-choice/implicit-case-container" {
        leaf leaf-after-container {
            type empty;
        }
    }

    augment "/my-choice/implicit-case-container/implicit-case-container" {
        leaf leaf-inside-container {
            type empty;
        }
    }

}
