module good6180 {

  namespace "odl:test:good6180";
  prefix "g";
  revision 2016-07-11;

  typedef double-quoted {
    type string {
      pattern '".*"';
    }
  }

  leaf foo {
    type string;
  }
  container bar {
    when '/foo != "bar"';
  }

}
