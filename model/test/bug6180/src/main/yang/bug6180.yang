module bug6180 {

  namespace "odl:test:bug6180";
  prefix "b";
  revision 2016-07-11;

  typedef double-quoted {
    type string {
      pattern "\".*\"";
    }
  }

  leaf foo {
    type string;
  }
  container bar {
    when "/foo != \"bar\"";
  }

}
