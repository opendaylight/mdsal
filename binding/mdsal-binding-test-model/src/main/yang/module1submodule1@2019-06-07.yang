submodule module1submodule1 {
    yang-version "1.1";
    belongs-to "module1" {
        prefix "module1";
    }

    include module1submodule2;

    revision "2019-06-07" {
    }

    grouping submodule1-grouping {
        leaf leaf1 {
            type string;
        }

        uses submodule2-grouping;
    }
}
