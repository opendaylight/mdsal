module a {
    yang-version 1;
    namespace "a";
    prefix "a";

    container foo {
        list bar {
            key name;
            leaf name {
                type string;
            }
        }
    }
}
