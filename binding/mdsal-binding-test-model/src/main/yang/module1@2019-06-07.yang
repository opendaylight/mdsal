module module1 {
    yang-version "1.1";
    namespace "urn:example:module1";
    prefix "module1";

    include module1submodule1;
    include module1submodule2;

    revision "2019-06-07" {
    }

    container cont1 {
        uses submodule1-grouping;
    }
}
