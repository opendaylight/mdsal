module mdsal-query {
  namespace "mdsal-query";
  prefix mq;

  typedef alarm-message {
    type string {
      length "1 .. 200";
    }
  }

  typedef alarm-union {
    type union {
      type uint32;

       type binary {
         length "3";
       }

       type string;

       type alarm-message;
    }
  }

  grouping first-grp {
    list system {
      key name;

      leaf name {
        type string;
      }

      leaf alias {
        type string;
      }

      uses second-grp;
    }
  }

  grouping second-grp {
    list alarms {
      key id;

      leaf id {
        type uint64;
      }

      leaf critical {
        type empty;
      }

      leaf-list alarm-messages {
        type alarm-message;
      }

      leaf-list alarm-unions {
        type alarm-union;
      }

      leaf-list primitive-messages {
        type string;
      }
      uses third-grp;
    }
  }

  grouping third-grp {
    list affected-users {
      key uid;

      leaf uid {
        type uint64;
      }

      leaf attr {
        type uint8;
      }
    }
  }

  container foo {
    uses first-grp;
  }
}
