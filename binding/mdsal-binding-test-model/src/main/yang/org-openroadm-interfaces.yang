module org-openroadm-interfaces {
    yang-version 1;
    namespace "dummy:org-openroadm-interfaces";
    prefix "org-openroadm-interfaces";

    revision 2021-04-26 {
        description "test";
    }

    identity interface-type {
      description
        "Base identity from which specific interface types are
         derived.";
    }

    identity ethernetCsmacd {
      base interface-type;
      description
        "For all Ethernet-like interfaces, regardless of speed,
         as per RFC 3635.";
      reference
        "RFC 3635 - Definitions of Managed Objects for the
                    Ethernet-like Interface Types";
    }
}
