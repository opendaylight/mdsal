module mdsal320 {
    namespace "urn:odl:mdsal320";
    prefix mdsal320;

    container foo {
        leaf bar {
            type union {
                type enumeration {
                    enum "foo";
                }
                type string {
                    length 2;
                }
                type union {
                    type enumeration {
                        enum bar;
                    }
                    type string {
                        length 1;
                    }
                }
            }
        }
    }
}
