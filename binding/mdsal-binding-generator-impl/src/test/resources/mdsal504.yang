module mdsal504 {
  yang-version 1.1;
  namespace "mdsal504";
  prefix "mdsal504";

  identity target-base;

  typedef target-type {
    type identityref {
      base target-base;
    }
  }

  grouping grp {
    leaf id {
      type string;
    }
    leaf type {
      type target-type;
    }

    list secondary {
      key "id type";
      leaf id {
        type leafref {
          path "/grp-uses/id";
        }
      }
      leaf type {
        type leafref {
          path "deref(../id)/../type";
        }
      }
    }
  }

  list grp-uses {
    uses grp;
    key "id type";
  }
}
