submodule child {

    belongs-to parent {
        prefix par;
    }

    import imported {
       prefix imp;
    }

    revision 2019-12-16 {
         description  "init";
    }

    container cont {
        leaf leaf1 {
            imp:bar "MY_LEAF1";
            type leafref {
                path "/imp:root/imp:leaf1";
            }
        }
        leaf leaf2 {
            type imp:foo;
        }
    }

}
