module test {
    namespace "urn:test";
    prefix tst;

    revision 2017-01-01;

    typedef id {
        type uint16 {
            range "1..4094";
        }
    }

    container cont {
        leaf vlan-id {
            type union {
                type id;
                type enumeration {
                    enum "any" {
                        value 4096;
                    }
                }
            }
            mandatory true;
        }
    }
}
