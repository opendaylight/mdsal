module mdsal502 {
  namespace mdsal502;
  prefix mdsal502;

  grouping MyGrp {
    leaf MyGrp {
      type string;
    }
  }

  grouping My_grp {
    leaf My_grp {
      type string;
    }
  }

  grouping my-grp {
    leaf my-grp {
      type string;
    }
  }

  grouping my.grp {
    leaf my.grp {
      type string;
    }
  }

  // neat conflict
  container my-grp {
    uses MyGrp;
    uses My_grp;
    uses my-grp;
    uses my.grp;
  }
}
