module mdsal718 {
  namespace mdsal718;
  prefix mdsal718;

  grouping foo {
    container foo;
  }

  uses foo {
    augment foo {
      container bar;
    }
  }

  augment /foo/bar {
    container baz;
  }
}
