module openconfig-mclag {

  yang-version "1";

  // namespace
  namespace "http://openconfig.net/yang/mclag/extension";

  prefix "oc-mclag";

  import openconfig-yang-types { prefix oc-yang; }
  import openconfig-inet-types { prefix oc-inet; }
  import openconfig-interfaces { prefix oc-if; }
  import openconfig-extensions { prefix oc-ext; }
  import openconfig-types { prefix oc-types; }

  // meta
  organization "OpenConfig working group";

  contact
    "OpenConfig working group
    www.openconfig.net";

  description
    "This module defines configuration and operational state data for Multi Chassis LAGs.
    MCLAG information are organized as MCLAG Domains.Each MCLAG Domain would contain
    config and state inforamtion of domain, it would contain mclag interfaces for that given domain";

  oc-ext:openconfig-version "1.0.2";

  revision "2019-12-02" {
    description
      "Initial revision";
    reference "TBD";
  }

  // OpenConfig specific extensions for module metadata.
  oc-ext:regexp-posix;
  oc-ext:catalog-organization "openconfig";
  oc-ext:origin "openconfig";

  // grouping statements

  grouping mclag-domain-config {
    description
      "MCLAG Domain config";

    leaf domain-id {
      type uint32 {
          range 1..4095;
      }
      description
        "Domain id for MCLAG Domain";
    }

    leaf source-address {
      type oc-inet:ip-address;

      description
        "source ip address of MCLAG Domain";
    }

    leaf peer-address {
      type oc-inet:ip-address;
      description
        "peer ip address of MCLAG Domain";
    }

    leaf peer-link {
      type string;
      description
        "peer link of MCLAG Domain";
    }

    leaf mclag-system-mac {
      type oc-yang:mac-address;
      description
        "MCLAG System MAC";
    }

    leaf keepalive-interval {
      type uint32 {
          range 1..60;
      }
      default 1;

      description
        "Keepalive interval for ICCP MCLAG session";
    }

    leaf session-timeout {
      type uint32 {
          range 1..3600;
      }
      default 30;

      description
        "Session Timeout for ICCP MCLAG session";
    }

    leaf delay-restore {
      type uint16 {
          range 1..3600;
      }
      units "seconds";
      default 300;
      description
        "Time to wait for protocol to converge before bringing up
        all MCLAG and orphan interfaces";
    }
  }

  grouping mclag-gateway-mac-config {
    description
      "MCLAG Domain config";
    leaf gateway-mac {
        type oc-yang:mac-address;
      description
        "Gateway Mac for MCLAG";
    }
}


  grouping mclag-domain-state {
    description
      "MCLAG Domain state";

    leaf oper-status {
      type enumeration {
        enum OPER_UP {
          description
            "MCLAG Session is operationally up";
        }
        enum OPER_DOWN {
          description
            "MCLAG Session is operationally down";
        }
     }
     description
       "MCLAG Domain Session oper status";
   }

   leaf role {
      type enumeration {
        enum ROLE_ACTIVE {
          description
            "MCLAG Node Role is Active";
        }
        enum ROLE_STANDBY {
          description
            "MCLAG Node Role is Standby";
        }
     }
     description
       "MCLAG Node's Role";
   }

   leaf system-mac {
     type oc-yang:mac-address;
     description
       "System MAC Address used for MCLAG Interface";
   }

   leaf delay-restore-start-time {
     type oc-types:timeticks64;
     units "seconds";
     description
       "Delay restore start time in seconds since the Epoch";
   }
 }

 grouping mclag-domain-top {
    description
      "MCLAG Domain variables top level container";

    container mclag-domains {
      description
        "MCLAG Domain entries variables enclosing container";

      list mclag-domain {
        key "domain-id";
        description
          "List of MCLAG Domain entries";

        leaf domain-id {
          type leafref {
            path "../config/domain-id";
          }
          description
            "Reference to the domain-id list  key";
        }

        container config {
          description
            "MCLAG Domain config";
          uses mclag-domain-config;

        }

        container state {
          config false;
          description
            "MCLAG Domain state information";
          uses mclag-domain-config;
          uses mclag-domain-state;
        }
      }
    }
  }


  grouping mclag-gateway-mac-top {
    description
      "MCLAG Gateway mac top level container";

    container mclag-gateway-macs {
      description
        "MCLAG Gateway MAC entries varaibles enclosing container";
      list mclag-gateway-mac {
        key "gateway-mac";
        max-elements 1;
        description
          "Gateway Mac for MCLAG";
        leaf gateway-mac {
            type leafref {
              path "../config/gateway-mac";
            }
            description
              "Reference to the gateway-mac list  key";
        }
        container config {
          description
            "MCLAG gw-mac config";
          uses mclag-gateway-mac-config;
        }
        container state {
          config false;
          description
            "MCLAG gw-mac config";
          uses mclag-gateway-mac-config;
        }
      }
    }
  }


  grouping mclag-interface-config {
    description
      "Configuration data for mclag interfaces";

    leaf name {
      type oc-if:base-interface-ref;
      description
        "Reference to the MCLAG LAG Interface";
    }

    leaf mclag-domain-id {
          /*type leafref {
            path "../../../../mclag-domains/mclag-domain/config/domain-id";
          }*/
          type uint32;
          description
            "Reference to MCLAG domain list key";
    }
    leaf mclag-id {
        type string;
    }
  }

  grouping mclag-interface-state {
    description
      "Operational state data for local interface references";

    container  local {
      description
         "Operational state for local interfaces";
      leaf traffic-disable {
        type boolean;
        default false;
        description
          "MCLAG local interface traffic disable value to indicate whether Tx/Rx traffic
          is disabled or enabled on this MCLAG interface";
      }

      leaf port-isolate {
        type boolean;
        default false;
        description
          "MCLAG local interface port isolation state to indicate whether BUM
          traffic incoming on ISL is blocked on MCLAG Interface";
      }

      leaf oper-status {
          type enumeration {
              enum OPER_UP {
                  description
                      "Local Interface operational status up";
              }
              enum OPER_DOWN {
                  description
                      "Local Interface operational status down";
              }
          }
          default OPER_DOWN;
          description
              "MCLAG Local Interface Operational status";
      }
    }
  }

  grouping mclag-remote-interface-state {
    description
      "Operational state data for remote interface references";

    container remote {
      description
        "Operational state data for remote interface references";
      leaf oper-status {
        type enumeration {
          enum OPER_UP {
            description
              "Remote Interface operational status up";
          }
          enum OPER_DOWN {
            description
              "Remote Interface operational status down";
          }
       }
       default OPER_DOWN;
       description
         "MCLAG Remote Interface Operational status";
      }
    }
  }


  grouping mclag-interfaces-top {
    description
      "Top-level grouping for MCLAG interface-specific data";

    container interfaces {
      description
        "Enclosing container for the list of interfaces on which
        MCLAG domains are enabled";

      list interface {
        key "name";
        description
          "List of interfaces on which MCLAG is configured";

        leaf name {
          type leafref {
            path "../config/name";
          }
          description
            "Reference to the interface id list key";
        }

        container config {
          description
            "Configuration for MCLAG per-interface data";

          uses mclag-interface-config;
        }

        container state {

          config false;

          description
            "Operational state for MCLAG interface data";

          uses mclag-interface-config;
          uses mclag-interface-state;
          uses mclag-remote-interface-state;
        }

      }
    }
  }

  grouping mclag-unique-ip-config {
    description
      "Configuration data for mclag unique ip";

    leaf name {
      type oc-if:base-interface-ref;
      description
        "Reference to the vlan routed Interface (SVI)";
    }

    leaf unique-ip-enable {
        type enumeration {
            enum ENABLE {
                description
                    "Enable MCLAG Unique-ip";
            }
        }
        description
            "unique ip enable, default : not enabled";
    }
  }

  grouping mclag-unique-ip-top {
    description
      "Top-level grouping for MCLAG unique-ip specific data";

    container vlan-interfaces {
      description
        "Enclosing container for the list of routed vlan
        interfaces on which MCLAG unique-ip are enabled";

      list vlan-interface {
        key "name";
        description
          "List of interfaces on which MCLAG unique-ip is configured";

        leaf name {
          type leafref {
            path "../config/name";
          }
          description
            "Reference to the interface id list key";
        }

        container config {
          description
            "Configuration for MCLAG unique-ip per vlan interface data";

          uses mclag-unique-ip-config;
        }

        container state {

          config false;

          description
            "Operational state for MCLAG unique-ip per
            vlan interface data";

          uses mclag-unique-ip-config;
        }
      }
    }
  }

  grouping mclag-config {
    description
      "Global configuration data for MCLAG";
  }

  grouping mclag-state {
    description
      "Global operational state data for MCLAG";
  }

  grouping mclag-top {
    description
      "Top level grouping for MCLAG data and structure";

    container mclag {
      description
        "Top level enclosing container for MCLAG model config
        and operational state data";

      container config {
        description
          "Global config data for MCLAG";
        uses mclag-config;
      }

      container state {

        config false;

        description
          "Global operational state data for MCLAG";

        uses mclag-config;
        uses mclag-state;
      }

      //mclag domain config and state
      uses mclag-domain-top;
      uses mclag-interfaces-top;
      uses mclag-unique-ip-top;
      uses mclag-gateway-mac-top;
    }
  }

  // data definition statements
  uses mclag-top;

  // augment statements
}
