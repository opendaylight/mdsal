module mdsal669 {
  namespace mdsal669;
  prefix mdsal669;

  grouping bar {
    container bar {
      leaf-list bar {
        type leafref {
          path ../../foo;
        }
      }
    }
  }

  container foo {
    leaf foo {
      type instance-identifier;
    }

    uses bar;
  }

  grouping baz {
    leaf baz {
      type leafref {
        path "../bar";
      }
    }
  }

  container one {
    leaf bar {
      type string;
    }
    uses baz;
  }

  container two {
    leaf bar {
      type uint16;
    }
    uses baz;
  }

  grouping unused {
    leaf foo {
      type leafref {
        path "../bar";
      }
    }
  }

  // this grouping is used ...
  grouping foo-as-string {
    leaf foo {
      type string;
    }

    uses bar;
  }

  // ... but this grouping is not ...
  grouping unused-bar {
    container qux {
      // ... and hence this is not count as an instantiation
      uses foo-as-string;
    }
  }
}
