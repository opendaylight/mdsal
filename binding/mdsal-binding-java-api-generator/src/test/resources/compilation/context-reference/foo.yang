/*
 * Copyright (c) 2013 Cisco Systems, Inc. and others.  All rights reserved.
 *
 * This program and the accompanying materials are made available under the
 * terms of the Eclipse Public License v1.0 which accompanies this distribution,
 * and is available at http://www.eclipse.org/legal/epl-v10.html
 */
module foo {
    yang-version 1;
    namespace "urn:opendaylight:foo";
    prefix "f";
    
    import bar { prefix "b"; }

    revision "2013-10-08" {
    }

    extension context-reference {
        argument "context-type";
    }

    container nodes {
        leaf id {
            type instance-identifier;
            f:context-reference "b:identity-class";
        }
        leaf-list constraints {
            type string;
        }
    }

}
