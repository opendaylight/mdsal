module complex {
    yang-version "1";
    namespace "urn:test:complex";
    prefix cx;
    description "complex-description";

    import simple {
        prefix sl;
        revision-date 2016-01-01;
    }

    include includedSubmodule;

    organization "simple-organization";
    contact "simple-contact";

    revision 2016-01-01 {
        description "complex yang";
        reference "initial complex yang reference";
    }

    typedef complex-typedef {
        description "complex-typedef description";
        reference "complex-typedef reference";
        units "complex-typedef units definition";
        default "complex-typedef default string";
        status "current";
        type union {
            type string {
                length "0..4";
                pattern "[0-9a-fA-F]*";
            }
            type bits {
                bit bit1 {
                    position 0;
                }
                bit bit2 {
                    position 1;
                }
            }
            type enumeration {
                enum enum1 {
                    value 1;
                }
                enum enum2 {
                    value 2;
                }
            }
            type int32 {
                range "11..max";
            }
        }
    }

    container complex-container-interface {
        presence "This is container with presence";
        leaf ifType {
            type enumeration {
                enum yes;
                enum no;
            }
        }
        leaf ifNumber {
            mandatory "true";
            type uint32;
            default 0;
            must "ifNumber < 10" {
                error-message "Number must be lesser than 10";
            }
        }
        must "ifType != 'no' or " + "(ifType = 'no' and ifNumber = 1)" {
            error-message "Number must be 1 or there must be YES";
        }

        choice complex-container-interface-choice {
            case complex-case-1 {
                choice complex-case-1-choice {
                    case complex-case-1-choice-case-1 {
                        leaf complex-case-1-choice-case-1-leaf {
                            type leafref {
                                path "/complex-container-interface/complex-container-interface-container/complex-container-interface-container-leaf1";
                            }
                        }
                    }
                    case complex-case-1-choice-case-2 {
                        leaf complex-case-1-choice-case-2-leaf {
                            type leafref {
                                path "/complex-container-interface/complex-container-interface-container/complex-container-interface-container-leaf2";
                            }
                        }
                    }
                }
            }
            case complex-case-2 {
                leaf complex-case-1-choice-case-1-leaf {
                    type string;
                }
            }
        }
        container complex-container-interface-container {
            leaf complex-container-interface-container-leaf1 {
                type string;
                default "complex-container-interface-container-leaf1";
            }
            leaf complex-container-interface-container-leaf2 {
                type string;
                default "complex-container-interface-container-leaf2";
            }
        }
    }

    leaf-list complex-leaflist {
        ordered-by user;
        type union {
            type string {
                length "0..5";
            }
            type enumeration {
                enum enum1 {
                    value 1;
                }
                enum enum2 {
                    value 2;
                }
            }
        }
        min-elements 1;
        max-elements 10;
        when "/complex-container-interface/ifType = yes";
    }

    list complex-list {
        key "complex-list-key complex-list-unique";
        unique "complex-list-choice";
        when "complex-list-unique != 2";
        config true;
        leaf complex-list-key {
            type string;
        }
        leaf complex-list-unique {
            type complex-typedef;
        }
        choice complex-list-choice {
            case complex-list-case-a {
                leaf a {
                    type string;
                }
            }
            case complex-list-case-b {
                leaf b {
                    type string;
                }
            }
            case complex-list-case-c {
                leaf c {
                    type string;
                }
            }
            container complex-list-case-c {
                uses complex-grouping {
                    augment grp-cont {
                        leaf complex-list-case-c-augmented-leaf {
                            type string;
                        }
                    }
                }
            }
        }
    }

    grouping complex-grouping {
        container grp-cont {
            description "old lf desc";
            reference "old lf ref";
            config true;
            leaf grp-lf {
                type string;
                description "old lf desc";
                reference "old lf ref";
                config true;
            }

            leaf-list grp-lls {
                type string;
                config true;
                must "old = o";
                min-elements 2;
                max-elements 4;
            }

            list grp-ls {
                config true;
                min-elements 2;
                max-elements 4;
            }

            choice grp-choice {
                default grp-choice1;
                case grp-choice1 {
                }
                case grp-choice2 {
                }
            }

            anyxml grp-axml {
                mandatory true;
            }

            uses submodule-included-grouping {
                refine submodule-included-grouping-leaf {
                    default "refined default value";
                }
            }
        }
    }

    notification notification-module1 {
        uses grouping-module1;
    }

    grouping grouping-module1 {
        list list-module1-1 {
            list list-module1-2 {
                container container-module1 {
                }
            }
        }
    }

    grouping uses-grouping-augmet-testgrouping-inner {
        container container-augmet-1 {
        }
    }

    grouping uses-grouping-augmet-testgrouping-outer {
        uses uses-grouping-augmet-testgrouping-inner {
            augment "container-augmet-1" {
                container container-2 {
                }
            }
        }
    }

    grouping uses-grouping-testgrouping-inner {
        container container-1 {
            container container-2 {
            }
        }
    }

    grouping uses-grouping-testgrouping-outer {
        uses uses-grouping-testgrouping-inner;
    }

    container container-augment {
        uses uses-grouping-augmet-testgrouping-outer;
    }

    container container-manual {
        uses uses-grouping-testgrouping-outer;
    }
}
