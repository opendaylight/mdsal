module mainYangTestImporting {
    namespace "urn:test:mainYangTestImporting";
    prefix myti;

    revision 2016-01-01 {
        description "imported yang for testing spec v2";
    }

    import mainYangTest {
        prefix imp;
        revision-date 2016-01-01;
    }

    augment "imp:main-cont" {
        leaf imported-augmented-leaf-1 {
            type string;
        }
    }

    augment "imp:main-cont" {
        leaf imported-augmented-leaf-2 {
            type string;
        }
    }

    container importing-container {
        uses main-group;
        augment "imp:main-group" {
            leaf imported-augmented-leaf-3 {
                type string;
            }
        }
    }
}
