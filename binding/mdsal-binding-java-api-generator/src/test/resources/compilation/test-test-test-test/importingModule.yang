module importingModule {
    namespace "urn:test:importedModule";
    prefix im;

    revision 2016-01-01 {
        description "importedtesting submodule";
    }

    import complex {
        prefix cx;
        revision-date 2016-01-01;
    }

    uses cx:complex-grouping {
        refine grp-cont {
            description "new lf desc";
            reference "new lf ref";
        }

        refine grp-cont/grp-lls {
            must "new = n";
            config false;
            min-elements 8;
            max-elements 10;
        }

        refine grp-cont/grp-ls {
            config false;
            min-elements 8;
            max-elements 10;
        }

        refine grp-cont/grp-axml {
            mandatory false;
        }
    }

    deviation cx:submodule-included-container/name {
        deviate replace {
            type string;
        }
        deviate add {
            default "new default";
        }
    }

    grouping grouping-module2 {
        container container-module2 {
        }
    }

    augment "/cx:notification-module1/cx:list-module1-1/cx:list-module1-2/cx:container-module1" {
        uses grouping-module2;
    }
}
