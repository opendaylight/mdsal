module missingAnyXml {
    namespace "urn:test:missingAnyXml";
    prefix may;

    revision 2016-01-01 {
        description "Bug 706 Missing support for anyxml statement in java
        generator and mapping service";
    }

    anyxml data {
        leaf test {
            type string;
        }
    }
}
