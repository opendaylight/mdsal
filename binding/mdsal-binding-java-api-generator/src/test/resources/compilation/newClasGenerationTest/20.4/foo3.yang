module foo3 {
    namespace "urn:test:foo3";
    prefix f3;

    revision 2016-01-01 {
        description "grouping key.grp.nodes.node.nodeidentifier
        instantiated key.data.nodes.node.nodeidentifier
        same solution applies for type and typedef as
        shown in comment";
    }


    grouping nodes {
//      typedef foo
        list node {
            key id;
            leaf id {
                leaf ref ?
            }
        }
    }



    container nodes {
//      type foo
        uses nodes;
    }
}
