module foo {
    namespace "urn:test:foo";
    prefix foo;

    revision 2016-01-01 {
        description "Bug 1466 Instance Identifier is unable to represent
        Choice / Case, only children ";
    }

    grouping foo {
        container bar {
        }
    }

    choice bar {
        case foo {
            uses foo;
        }
    }
}
