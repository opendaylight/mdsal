module augmentedContainer {
    namespace "urn:test:augmentedContainer";
    prefix ac;

    revision 2016-01-01 {
        description "Bug 1644 - InstanceIdentifier does not properly capture choice-case child relationship";
    }

    grouping linkstate-routes {
        container linkstate-routes {
            list linkstate-route {
            }
        }
    }

    augment test-choice {
        case linkstate-routes-case {
            uses linkstate-routes;
        }
    }

    choice test-choice {
        case test-case {
            leaf test-leaf {
                type string;
            }
        }
    }
}
