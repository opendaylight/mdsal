module listKeyKey {
    namespace "urn:test:listKeyKey";
    prefix lkk;

    revision 2016-01-01 {
        description "bug 157 key with name key";
    }

    list example {
        key "key";
        leaf key {
            type string;
        }
    }
}
