module foo2 {
    namespace "urn:test:foo2";
    prefix f2;

    revision 2016-01-01 {
        description "list foo - data.Foo
        key identifier - key.foo.FooIdentifier,
        type union - type.foo.identifier.IdentifierUnion,
        type    - global
                - grouping
                - union, enum, bits
        container foo-identifier - data.FooIdentifier,
        typedef foo-identifier - type.FooIdentifier";
    }

    list foo {
        key identifier;
        leaf identifier {
            type union {
                type string;
            }
        }
    }

    container foo-identifier {
    }

    typedef foo-identifier {
    }
}
