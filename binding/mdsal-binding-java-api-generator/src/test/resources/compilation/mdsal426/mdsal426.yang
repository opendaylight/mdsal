module mdsal426 {
  yang-version 1;
  namespace "mdsal426";
  prefix "mdsal426";

  grouping foo_grp {
    leaf leaf1 {
      type leafref {
        path "../mdsal426:name";
      }
    }
    leaf leaf2 {
      type string;
    }
  }

  grouping bar_grp {
    uses foo_grp;
    leaf name {
        type string;
    }
  }

  container bar_cont {
    uses bar_grp;
  }

  grouping baz_grp {
    uses bar_grp;
  }

  container baz_cont {
    uses baz_grp;
  }
}
