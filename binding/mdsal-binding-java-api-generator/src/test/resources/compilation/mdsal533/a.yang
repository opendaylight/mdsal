module bar {
  yang-version 1;
  namespace "bar";
  prefix "bar";

  grouping foo_grp {
    leaf key_leaf1 {
      type leafref {
        path "../../../bar:foo_list/bar:name";
      }
    }
    leaf key_leaf2 {
      type string;
    }
    leaf key_leaf3 {
      type string;
    }
  }

  container foo_cont {
    list foo_list {
      key "name";
      leaf name {
        type string {
          length "1..255";
        }
      }
    }
    container foo_cont2 {
      list foo_list2 {
        key "key_leaf1 key_leaf2 key_leaf3";
        uses foo_grp;
      }
    }
  }
}
