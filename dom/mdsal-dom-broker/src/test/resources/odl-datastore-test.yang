module odl-datastore-test {
    yang-version 1;
    namespace "urn:opendaylight:params:xml:ns:yang:controller:md:sal:dom:store:test";
    prefix "store-test";

    revision "2014-03-13" {
        description "Initial revision.";
    }

    container test {
        presence "presence container";
        list outer-list {
            key id;
            leaf id {
                type uint16;
            }
            choice outer-choice {
                case one {
                    leaf one {
                        type string;
                    }
                }
                case two-three {
                    leaf two {
                        type string;
                    }
                    leaf three {
                        type string;
                    }
               }
           }
           list inner-list {
                key name;
                leaf name {
                    type string;
                }
                leaf value {
                    type string;
                }
            }
        }

        container inner-container {

            leaf sharded-value-1 {
                type string;
            }

            leaf sharded-value-2 {
                type string;
            }

            container another-shard {
                list new-shard-list {
                    key name;
                    leaf name {
                        type string;
                    }
                    leaf value {
                        type string;
                    }
                }

                leaf another-shard-value {
                    type string;
                }
            }
        }
    }

    container test2 {
    }
}
