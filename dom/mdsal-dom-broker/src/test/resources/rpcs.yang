module rpcs {
  namespace rpcs;
  prefix rpcs;

  import yang-ext {
    prefix ext;
  }

  rpc foo;

  identity context-type;

  rpc bar {
    input {
      leaf ctx {
        type instance-identifier;
        ext:context-reference context-type;
      }
    }
  }

  list baz {
    key name;
    leaf name {
      type string;
    }

    ext:context-instance context-type;
  }
}
