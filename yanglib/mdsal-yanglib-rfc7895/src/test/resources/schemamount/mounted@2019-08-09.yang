module mounted {

    yang-version 1.1;

    namespace "urn:example:mounted";
    prefix "mounted";

    revision "2019-08-09" {
        description "Intial revision";
    }

    container interfaces {
        list interface {
            key "name";
            leaf name {
                type string;
            }
        }
    }
}
