module odl-datastore-test {
    yang-version 1;
    namespace "urn:opendaylight:params:xml:ns:yang:controller:md:sal:dom:store:test";
    prefix "store-test";

    revision "2014-03-13" {
        description "Initial revision.";
    }

    container test {
        list outer-list {
            key id;
            leaf id {
                type int32;
            }
            choice outer-choice {
                case one {
                    leaf one {
                        type string;
                    }
                }
                case two-three {
                    leaf two {
                        type string;
                    }
                    leaf three {
                        type string;
                    }
               }
           }
           list inner-list {
                key name;
                leaf name {
                    type int32;
                }
                leaf value {
                    type string;
                }
            }
        }
    }
}
